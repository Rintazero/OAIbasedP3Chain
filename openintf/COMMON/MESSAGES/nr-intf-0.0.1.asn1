-- TAG-NR-INTF-DEFINITIONS-SRART

NR-INTF-Definitions DEFINITIONS AUTOMATIC TAGS ::=

BEGIN

-- TAG-NR-INTF-DEFINITIONS-STOP
-- TAG-INTF-TEST-MESSAGE-START

INTF-TEST-Message ::=           SEQUENCE {
    int-data                        INTEGER(0..255)
}

-- TAG-INTF-TEST-MESSAGE-STOP

END
